FME workspace Zadanie3.fmw

Parameters:
- SourceDataset_SHAPEFILE = C:\Studia\BDP_dane\bdline_essh_gb\Data\GB\scotland_and_wales_region.shp   # Source Esri Shapefile(s)
- SourceDataset_GEOTIFF = ""C:\Studia\BDP_dane\ras250_gb\ras250_gb\data\HP.tif" "C:\Studia\BDP_dane\ras250_gb\ras250_gb\data\HT.tif" "C:\Studia\BDP_dane\ras250_gb\ras250_gb\data\HU.tif" "C:\Studia\BDP_dane\ras250_gb\ras250_gb\data\HW.tif" "C:\Studia\BDP_dane\ras250_gb\ras250_gb\data\HX.tif" "C:\Studia\BDP_dane\ras250_gb\ras250_gb\data\HY.tif" "C:\Studia\BDP_dane\ras250_gb\ras250_gb\data\HZ.tif" "C:\Studia\BDP_dane\ras250_gb\ras250_gb\data\NA.tif" "C:\Studia\BDP_dane\ras250_gb\ras250_gb\data\NB.tif" "C:\Studia\BDP_dane\ras250_gb\ras250_gb\data\NC.tif" "C:\Studia\BDP_dane\ras250_gb\ras250_gb\data\ND.tif" "C:\Studia\BDP_dane\ras250_gb\ras250_gb\data\NF.tif" "C:\Studia\BDP_dane\ras250_gb\ras250_gb\data\NG.tif" "C:\Studia\BDP_dane\ras250_gb\ras250_gb\data\NH.tif" "C:\Studia\BDP_dane\ras250_gb\ras250_gb\data\NJ.tif" "C:\Studia\BDP_dane\ras250_gb\ras250_gb\data\NK.tif" "C:\Studia\BDP_dane\ras250_gb\ras250_gb\data\NL.tif" "C:\Studia\BDP_dane\ras250_gb\ras250_gb\data\NM.tif" "C:\Studia\BDP_dane\ras250_gb\ras250_gb\data\NN.tif" "C:\Studia\BDP_dane\ras250_gb\ras250_gb\data\NO.tif" "C:\Studia\BDP_dane\ras250_gb\ras250_gb\data\NR.tif" "C:\Studia\BDP_dane\ras250_gb\ras250_gb\data\NS.tif" "C:\Studia\BDP_dane\ras250_gb\ras250_gb\data\NT.tif" "C:\Studia\BDP_dane\ras250_gb\ras250_gb\data\NU.tif" "C:\Studia\BDP_dane\ras250_gb\ras250_gb\data\NW.tif" "C:\Studia\BDP_dane\ras250_gb\ras250_gb\data\NX.tif" "C:\Studia\BDP_dane\ras250_gb\ras250_gb\data\NY.tif" "C:\Studia\BDP_dane\ras250_gb\ras250_gb\data\NZ.tif" "C:\Studia\BDP_dane\ras250_gb\ras250_gb\data\OV.tif" "C:\Studia\BDP_dane\ras250_gb\ras250_gb\data\SC.tif" "C:\Studia\BDP_dane\ras250_gb\ras250_gb\data\SD.tif" "C:\Studia\BDP_dane\ras250_gb\ras250_gb\data\SE.tif" "C:\Studia\BDP_dane\ras250_gb\ras250_gb\data\SH.tif" "C:\Studia\BDP_dane\ras250_gb\ras250_gb\data\SJ.tif" "C:\Studia\BDP_dane\ras250_gb\ras250_gb\data\SK.tif" "C:\Studia\BDP_dane\ras250_gb\ras250_gb\data\SM.tif" "C:\Studia\BDP_dane\ras250_gb\ras250_gb\data\SN.tif" "C:\Studia\BDP_dane\ras250_gb\ras250_gb\data\SO.tif" "C:\Studia\BDP_dane\ras250_gb\ras250_gb\data\SP.tif" "C:\Studia\BDP_dane\ras250_gb\ras250_gb\data\SR.tif" "C:\Studia\BDP_dane\ras250_gb\ras250_gb\data\SS.tif" "C:\Studia\BDP_dane\ras250_gb\ras250_gb\data\ST.tif" "C:\Studia\BDP_dane\ras250_gb\ras250_gb\data\SU.tif" "C:\Studia\BDP_dane\ras250_gb\ras250_gb\data\SV.tif" "C:\Studia\BDP_dane\ras250_gb\ras250_gb\data\SW.tif" "C:\Studia\BDP_dane\ras250_gb\ras250_gb\data\SX.tif" "C:\Studia\BDP_dane\ras250_gb\ras250_gb\data\SY.tif" "C:\Studia\BDP_dane\ras250_gb\ras250_gb\data\SZ.tif" "C:\Studia\BDP_dane\ras250_gb\ras250_gb\data\TA.tif" "C:\Studia\BDP_dane\ras250_gb\ras250_gb\data\TF.tif" "C:\Studia\BDP_dane\ras250_gb\ras250_gb\data\TG.tif" "C:\Studia\BDP_dane\ras250_gb\ras250_gb\data\TL.tif" "C:\Studia\BDP_dane\ras250_gb\ras250_gb\data\TM.tif" "C:\Studia\BDP_dane\ras250_gb\ras250_gb\data\TQ.tif" "C:\Studia\BDP_dane\ras250_gb\ras250_gb\data\TR.tif" "C:\Studia\BDP_dane\ras250_gb\ras250_gb\data\TV.tif""   # Source GeoTIFF File(s) or URL(s)
- DestDataset_POSTGIS_RASTER = Exports   # Connection

Readers:
- SHAPEFILE_1: SHAPEFILE from $(SourceDataset_SHAPEFILE)
- GEOTIFF_1: GEOTIFF from $(SourceDataset_GEOTIFF)

Writers:
- POSTGIS_RASTER_1: POSTGIS_RASTER to $(DestDataset_POSTGIS_RASTER)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES double, AREA double, TYPE_CODE varchar(2), DESCRIPT0 varchar(25), TYPE_COD0 varchar(3), DESCRIPT1 varchar(36)
    -> Tester
Tester
    BOOL_OP = OR
    TEST_CLAUSE = CASE_INSENSITIVE_TEST @Value(FILE_NAME) CONTAINS SOUTH_WALES
    TEST_MODE = CASE_INSENSITIVE_TEST
    PASSED -> Clipper [CLIPPER]
GEOTIFF (reader GEOTIFF_1)
    -> RasterPaletteResolver
RasterPaletteResolver
    -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Exports (writer POSTGIS_RASTER_1)
Exports (writer POSTGIS_RASTER_1)
    attributes: _clipped char(3)
